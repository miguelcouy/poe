CORREIO DEFINITIONS ::=
BEGIN

--falta enum ou ajustar choice pra utilizar dentro da class

MEDIDA ::= CHOICE {
	jardas REAL,
	pes    REAL,
	polegadas REAL
}
		
TAMANHODECAIXA ::= CLASS {
	&medida MEDIDA, 
	&altura REAL,
	&largura REAL,
	&comprimento REAL
	
} WITH SYNTAX { MEDIDA &medida, ALTURA &altura, LARGURA &largura, COMPRIMENTO &comprimento}

CAIXA ::= SEQUENCE {
	medida      	 TAMANHODECAIXA.&medida (MEDIDA.jardas(100)),
	altura      	 TAMANHODECAIXA.&altura (100),
	largura      	 TAMANHODECAIXA.&largura (100),
	comprimento      TAMANHODECAIXA.&comprimento (100)
}

END
